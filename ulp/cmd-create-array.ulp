/*
  Simple way of laying out parts in a 1D (for now array).

  TO DO:
  - Create an array of parts in schematic
  - Create an array of pads / or whatever in package editor
  - 2D Arrays
  - Radial arrays
  

  v@2000db.com
  
 */

// DLG
string help = "\nSelect parts you wish to layout in array\n" +
    "either using a group, or calling the command\n" +
    "with a name and lower and upper bounds (i.e. LED1 - LED10).\n" +
    "The array will start at the specified coordinates\n" +
    "incrementing at the specified regular intervals\n";

string version = "001";

int isByGroup = 0;
int isByName = 0;


// Array
real startX = 0.0;
real incrementX = 10;
real startY = 0.0;
real incrementY = 0.0;

string cmd = "";
int count = 0;

// Part selection
string partName = "";
int lowerBound = 0;
int upperBound = 0;


void createArray() {
    if(board)
        board(B) {
            B.elements(E) {
                if(ingroup(E) && isByGroup) {
                    string s = "";
                    real x, y;
                    x = incrementX * count + startX;
                    y = incrementY * count + startY;
                    sprintf(s, "MOVE %s (%f %f);", E.name, x, y);
                    cmd += s;
                    count++;
                }
                else if(isByName) {
                    if(strtol(strsub(E.name, strlen(partName))) >= lowerBound &&
                       strtol(strsub(E.name, strlen(partName))) <= upperBound &&
                       strsub(E.name, 0, strlen(partName)) == partName) {
                        string s = "";
                        real x, y;
                        x = incrementX * count + startX;
                        y = incrementY * count + startY;
                        sprintf(s, "MOVE %s (%f %f);", E.name, x, y);
                        cmd += s;
                        count++;
                    }
                }
            }
        }
    return;
}

if(argc == 6)
{
    startX = strtod(argv[2]);
    startY = strtod(argv[3]);
    incrementX = strtod(argv[4]);
    incrementY = strtod(argv[5]);
    createArray();
}
else {
    dlgDialog("Create 1D Array")
    {
        dlgGroup("Mode") {
            dlgRadioButton("Select by Group", isByGroup);
            dlgRadioButton("Select by Name", isByName);
        }
        dlgGroup("Name selection - use only if selecting by name") {
            dlgHBoxLayout {
                dlgLabel("&Part Name");
                dlgStringEdit(partName);
                dlgStretch(1);
            }
            dlgHBoxLayout {
                dlgLabel("&Lower Limit");
                dlgIntEdit(lowerBound);
                dlgStretch(1);
            }
            dlgHBoxLayout {
                dlgLabel("&Upper Limit");
                dlgIntEdit(upperBound);
                dlgStretch(1);
            }
        }
        dlgGroup("Array Parameters") {
            dlgHBoxLayout {
                dlgLabel("&X start position");
                dlgRealEdit(startX, -1000, 1000);
                dlgStretch(1);
            }
            dlgHBoxLayout {
                dlgLabel("&Y start position");
                dlgRealEdit(startY, -1000, 1000);
                dlgStretch(1);
            }
            dlgHBoxLayout {
                dlgLabel("&X position increment");
                dlgRealEdit(incrementX, -100, 100);
                dlgStretch(1);
            }
            dlgHBoxLayout {
                dlgLabel("&Y position increment");
                dlgRealEdit(incrementY, -100, 100);
                dlgStretch(1);
            }
        }
        dlgLabel(help);
        dlgLabel("Version "+version);
        dlgHBoxLayout {
            dlgPushButton("+OK") 
            {
                createArray();
                dlgAccept();
            }
            dlgPushButton("-&Cancel") exit(0);
            dlgStretch(0);
        }
    };
}

exit(cmd);
