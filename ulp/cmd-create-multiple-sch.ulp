/*
  Take a part or group in the schematic and duplicate it a certain number of times by cutting and pasting.
  Spacing can be specified.

  v@2000db.com
  
 */

string help = "\n Select parts you wish to duplicate\n";
    
string version = "001";

string script_name;

real startX = 0.0;
real incrementX = 10;
real startY = 0.0;
real incrementY = 0.0;

string cmd = "";
int count = 0;

void duplicate() {
    if(schematic)
        schematic(S) {
            S.parts(P) {
                P.instances(S) {
                    if(ingroup(S)) {
                        string s = "";
                        real x, y;
                        x = incrementX * count + startX;
                        y = incrementY * count + startY;
                        sprintf(s, "COPY (%f %f) (%f %f);", u2mm(S.x), u2mm(S.y), 0, 0);
                        cmd += s;
                        count++;
                    }
                }
            }
        }
    return;
}

/* // Fill this via dialog box */

if(argc == 6)
{
    startX = strtod(argv[2]);
    startY = strtod(argv[3]);
    incrementX = strtod(argv[4]);
    incrementY = strtod(argv[5]);
    duplicate();
}
else {
    dlgDialog("Create 1D Array")
    {
        dlgGroup("Array Parameters") {
            dlgHBoxLayout {
                dlgLabel("&X start position");
                dlgRealEdit(startX, -1000, 1000);
                dlgStretch(1);
            }
            dlgHBoxLayout {
                dlgLabel("&Y start position");
                dlgRealEdit(startY, -1000, 1000);
                dlgStretch(1);
            }
            dlgHBoxLayout {
                dlgLabel("&X position increment");
                dlgRealEdit(incrementX, -100, 100);
                dlgStretch(1);
            }
            dlgHBoxLayout {
                dlgLabel("&Y position increment");
                dlgRealEdit(incrementY, -100, 100);
                dlgStretch(1);
            }
        }
        dlgLabel(help);
        dlgLabel("Version "+version);
        dlgHBoxLayout {
            dlgPushButton("+OK") 
            {
                duplicate();
                dlgAccept();
            }
            dlgPushButton("-&Cancel") exit(0);
            dlgStretch(0);
        }
    };
}

/* output(script_name, "wtD") printf(cmd); // WHAAA */
/* string s; */
/* sprintf(s, "SCRIPT '%s'\n;", script_name); */
exit(cmd);
